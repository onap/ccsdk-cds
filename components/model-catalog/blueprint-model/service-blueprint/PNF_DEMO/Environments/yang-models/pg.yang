module sample-plugin {

    yang-version 1;
    namespace "urn:opendaylight:params:xml:ns:yang:sample-plugin";
    prefix "sample-plugin";

    description
        "This YANG module defines the generic configuration and
        operational data for sample-plugin in VPP";

    revision "2016-09-18" {
        description "Initial revision of sample-plugin model";
    }

    container sample-plugin {
        uses sample-plugin-params;
        description "Configuration data of sample-plugin in Honeycomb";

        // READ
        // curl -u admin:admin http://localhost:8181/restconf/config/sample-plugin:sample-plugin

        // WRITE
        // curl http://localhost:8181/restconf/operational/sample-plugin:sample-plugin

    }

    grouping sample-plugin-params {
        container pg-streams {
            list pg-stream {

                key id;
                leaf id {
                    type string;
                }

                leaf is-enabled {
                  type boolean;
                }
            }
        }
    }
}
